DABING-MIB DEFINITIONS ::= BEGIN

--
-- MIB objects for Dabing+ project
--

IMPORTS
    MODULE-IDENTITY, Integer32, OBJECT-TYPE, enterprises
        FROM SNMPv2-SMI;

dabing MODULE-IDENTITY
    LAST-UPDATED "202203170000Z"
    ORGANIZATION "www.stuba.sk"
    CONTACT-INFO "email: xsvajkaj@stuba.sk"
    DESCRIPTION
        "MIB objects for Dabing+ project"
    REVISION
        "202203170000Z"
    DESCRIPTION
        "First Draft"
    ::= { enterprises 55532 }


-- Structure (Starts: 1.3.6.1.4.1.55532...)
-- [1]: dabing
--     [1]: Parameters
--         [1]: channel
--         [2]: interval
--         [3]: trapEnabled
--     [2]: Agent
--         [1]: agentIdentifier
--         [2]: agentLabel
--         [3]: agentStatus
--     [3]: Manager
--         [1]: managerHostname
--         [2]: managerPort
--     [4]: Notifications
--         [1]: NotificationPrefix
--             [1]: malfunctionTrap
--             [2]: testTrap
--         [2]: NotificationObjects
--             [1]: genericPayload


Parameters                OBJECT IDENTIFIER ::= { dabing 1 }
Agent                     OBJECT IDENTIFIER ::= { dabing 2 }
Manager                   OBJECT IDENTIFIER ::= { dabing 3 }
Notifications             OBJECT IDENTIFIER ::= { dabing 4 }

NotificationPrefix        OBJECT IDENTIFIER ::= { Notifications 1 }
NotificationObjects       OBJECT IDENTIFIER ::= { Notifications 2 }

--
-- Parameters
--

channel OBJECT-TYPE
    SYNTAX      OCTET STRING
    MAX-ACCESS  read-only
    STATUS      current
    DESCRIPTION
        "This is a read-only object which is a OCTET STRING. It's value
         indicates the Channel of Digital Audio Broadasting which it
         is monitoring. In order to change this value, follow the
         instructions at the device's website."
    DEFVAL { "12C" }
    ::= { Parameters 1 }

interval OBJECT-TYPE
    SYNTAX      Integer32
    MAX-ACCESS  read-only
    STATUS      current
    DESCRIPTION
        "This is a read-only object which is an Integer32. It's value
         indicates period of saving the data to the database.
         This value shall be multiple of 96 which is the duration of
         one Digital Audio Broadcasting frame.
         In order to change this value, follow the
         instructions at the device's website."
    DEFVAL { 960 }
    ::= { Parameters 2 }

trapEnabled OBJECT-TYPE
    SYNTAX      Integer32
    MAX-ACCESS  read-only
    STATUS      current
    DESCRIPTION
        "This is a read-only object which is an Integer32. It's value
         indicates whether the monitoring device is allowed to send
         'malfunctionTrap' trap. ( false=0 | true=1 )"
    ::= { Parameters 3 }


--
-- Agent
--

agentIdentifier OBJECT-TYPE
    SYNTAX      Integer32
    MAX-ACCESS  read-write
    STATUS      current
    DESCRIPTION
        "This is a read-write object which is an Integer32.
        It is a unique integer used to distinguish
        agents from each other in a network. The value
        is included in every notification message."
    ::= { Agent 1 }

agentLabel OBJECT-TYPE
    SYNTAX      OCTET STRING
    MAX-ACCESS  read-write
    STATUS      current
    DESCRIPTION
        "This is a read-write object which is a OCTET STRING.
        It is a unique label used to distinguish
        agents from each other in a network. The value
        is included in every notification message."
    ::= { Agent 2 }

agentStatus OBJECT-TYPE
    SYNTAX      Integer32
    MAX-ACCESS  read-only
    STATUS      current
    DESCRIPTION
        "This is a read-only object which is an Integer32.
         The value indicates whether the device is working ok.
         ( false=0 | true=1 )"
    ::= { Agent 3 }


--
-- Manager
--

managerHostname OBJECT-TYPE
    SYNTAX      OCTET STRING
    MAX-ACCESS  read-only
    STATUS      current
    DESCRIPTION
        "This is a read-only object which is a OCTET STRING.
         The value represents IP address of the SNMP manager.
         In order to change this value, follow the
         instructions at the device's website."
    ::= { Manager 1 }

managerPort OBJECT-TYPE
    SYNTAX      Integer32
    MAX-ACCESS  read-only
    STATUS      current
    DESCRIPTION
        "This is a read-only object which is an Integer32.
         The value represents the port of the SNMP manager
         dedicated to traps.
         In order to change this value, follow the
         instructions at the device's website."
    DEFVAL { 162 }
    ::= { Manager 2 }


--
-- Notification Objects
--

genericPayload OBJECT-TYPE
    SYNTAX      OCTET STRING
    MAX-ACCESS  accessible-for-notify
    STATUS      current
    DESCRIPTION
        "This is a accessible-for-notify object which is a OCTET STRING.
         This object is a placeholder for any trap."
    ::= { NotificationObjects 1 }


--
-- Notification Prefix
--

malfunctionTrap NOTIFICATION-TYPE
    OBJECTS { genericPayload }
    STATUS  current
    DESCRIPTION
        "A trap notification used when quality indicators of the broadcasting
         are out of range. The specific range of every quality indicator is
         specified in alarm configuration. Therefore, make sure that you
         set up alarm configuration properly before starting the monitoring device!"
    ::= { NotificationPrefix 1 }

testTrap NOTIFICATION-TYPE
    OBJECTS { genericPayload }
    STATUS  current
    DESCRIPTION
        "A trap notification used when testing the agent-manager communication."
    ::= { NotificationPrefix 2 }

END
