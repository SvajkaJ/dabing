DABING-MIB DEFINITIONS ::= BEGIN

--
-- MIB objects for Dabing+ project
--

IMPORTS
    MODULE-IDENTITY, Integer32, OBJECT-TYPE, enterprises
        FROM SNMPv2-SMI;

dabing MODULE-IDENTITY
    LAST-UPDATED "202010210000Z"
    ORGANIZATION "www.stuba.sk"
    CONTACT-INFO "email: xsvajkaj@stuba.sk"
    DESCRIPTION
        "MIB objects for Dabing+ project"
    REVISION
        "202010210000Z"
    DESCRIPTION
        "First Draft"
    ::= { enterprises 55532 }


-- Structure (Starts: 1.3.6.1.4.1.55532...)
-- [1]: dabing
--     [1]: dabingParameters
--         [1]: dabingChannel
--         [2]: dabingInterval
--     [2]: dabingAgentInfo
--         [1]: dabingAgentIdentifier
--         [2]: dabingAgentHostname
--         [3]: dabingAgentLocation
--         [4]: dabingAgentStatus
--     [3]: dabingNotifications
--         [1]: dabingNotificationPrefix
--             [1]: dabingMalfunctioningBroadcastingTrap
--             [2]: dabingTestTrap
--         [2]: dabingNotificationObjects
--             [1]: dabingGenericPayload
--             [2]: dabingPowerSpectralDensity


dabingParameters                OBJECT IDENTIFIER ::= { dabing 1 }
dabingAgentInfo                 OBJECT IDENTIFIER ::= { dabing 2 }
dabingNotifications             OBJECT IDENTIFIER ::= { dabing 3 }

dabingNotificationPrefix        OBJECT IDENTIFIER ::= { dabingNotifications 1 }
dabingNotificationObjects       OBJECT IDENTIFIER ::= { dabingNotifications 2 }

--
-- Dabing Parameters
--

dabingChannel OBJECT-TYPE
    SYNTAX      OCTET STRING
    MAX-ACCESS  read-write
    STATUS      current
    DESCRIPTION
        "This is a simple object which is a OCTET STRING. It's value
         indicates the Channel of Digital Audio Broadasting which it
         should monitor. Changing it's value will change the frequency
         at which the device performs monitoring.

         Note that not all values are possible due to the tuner's 
         properties on receiver's side."
    DEFVAL { "12C" }
    ::= { dabingParameters 1 }

dabingInterval OBJECT-TYPE
    SYNTAX      OCTET STRING
    MAX-ACCESS  read-write
    STATUS      current
    DESCRIPTION
        "This is a simple object which is a OCTET STRING. It's value
         indicates interval at which the data should be saved to database"
    DEFVAL { "960" }
    ::= { dabingParameters 2 }


--
-- Dabing Device Info
--

dabingAgentIdentifier OBJECT-TYPE
    SYNTAX      Integer32
    MAX-ACCESS  read-write
    STATUS      current
    DESCRIPTION
        "Unique integer used for identifying the specific agent."
    ::= { dabingAgentInfo 1 }

dabingAgentHostname OBJECT-TYPE
    SYNTAX      OCTET STRING
    MAX-ACCESS  read-only
    STATUS      current
    DESCRIPTION
        "A host name that exists in the /etc/hosts (unix) file."
    ::= { dabingAgentInfo 2 }

dabingAgentLocation OBJECT-TYPE
    SYNTAX      OCTET STRING
    MAX-ACCESS  read-only
    STATUS      current
    DESCRIPTION
        "Physical location of the device. It can be described
         either by name of the location, GPS location or etc."
    ::= { dabingAgentInfo 3 }

dabingAgentStatus OBJECT-TYPE
    SYNTAX      Integer32
    MAX-ACCESS  read-only
    STATUS      current
    DESCRIPTION
        "Represent the current status of the device or
         if used in a trap then the status of the malfunction."
    ::= { dabingAgentInfo 4 }


--
-- Dabing Notification Objects
--

dabingGenericPayload OBJECT-TYPE
    SYNTAX      OCTET STRING
    MAX-ACCESS  accessible-for-notify
    STATUS      current
    DESCRIPTION
        "A simple generic OCTET STRING object, to act as a payload of any trap."
    DEFVAL { "TEST" }
    ::= { dabingNotificationObjects 1 }

dabingPowerSpectralDensity OBJECT-TYPE
    SYNTAX      OCTET STRING
    MAX-ACCESS  accessible-for-notify
    STATUS      current
    DESCRIPTION
        "A simple OCTET STRING object, to act as a payload for the
         DabingMalfunctioningBroadcastingTrap. The value is usually
         a floating point number expressing calculated 
         Power Spectral Density of the broadcasting tower."
    DEFVAL { "0.0" }
    ::= { dabingNotificationObjects 2 }


--
-- Dabing Notification Prefix
--

dabingMalfunctioningBroadcastingTrap NOTIFICATION-TYPE
    OBJECTS { dabingPowerSpectralDensity }
    STATUS  current
    DESCRIPTION
        "A notification used when the broadcasting tower senses a malfunction."
    ::= { dabingNotificationPrefix 1 }

dabingTestTrap NOTIFICATION-TYPE
    OBJECTS { dabingGenericPayload }
    STATUS  current
    DESCRIPTION
        "A notification used when testing the agent-manager communication."
    ::= { dabingNotificationPrefix 2 }

END
